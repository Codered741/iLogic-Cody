'v1.1 20181116 Updated to name stl file as part number, not file name.  per request by JO on 20181001
'v1.0 initial release
Imports System.IO
Imports System.IO.Path
Imports System.Collections


Sub Main()
'declarations
	Dim oDoc as Document
	Dim compOcc as ComponentOccurrence
	customPropertySet = ThisDoc.Document.PropertySets.Item("Inventor User Defined Properties")
	
'Main
	oDoc = ThisApplication.ActiveEditDocument
	
	If oDoc.FileSaveCounter >= 1 Then
		' Are we in a Assembly or Part Document?
		If oDoc.DocumentType = kAssemblyDocumentObject Or oDoc.DocumentType = kPartDocumentObject Then
			
			Dim CurDate as Date = DateTime.Now 'pull current date stamp		
			
			strlongDate = CurDate.ToString("D")
			
			Dim folderDate as Date
			
			If strlongDate.Contains("Saturday") = True Then
				folderDate = DateAndTime.DateAdd(DateInterval.Day, 2, CurDate)
			Else If strlongDate.Contains("Sunday") = True Then
				folderDate = DateAndTime.DateAdd(DateInterval.Day, 1, CurDate)
			Else 
				folderDate = CurDate
			End If
			
			DateFolder = folderDate.ToString("yyyyMMdd")
			'oPath = "C:\TESTING\" & DateFolder 'use this to test
			oPath = "\\RD-Zeus\MultiJet Print Queue\" & DateFolder
			Try 
				System.IO.Directory.CreateDirectory(oPath)
			Catch
				MessageBox.Show("There was a problem accessing the network location.  The rule cannot continue.  Please make sure that " & oPath & " is available.  ",  "Network Access Error", MessageBoxButtons.OK, MessageBoxIcon.Error)
				Exit Sub
			End Try
			
			'v1.1 change
			oFileName = oDoc.PropertySets.Item("Design Tracking Properties").Item("Part Number").Value 'IO.Path.GetFileNameWithoutExtension(oDoc.FullFileName)
			
			'Get STL translator, and set options for export
			oSTLAddIn = ThisApplication.ApplicationAddIns.ItemById("{81CA7D27-2DBE-4058-8188-9136F85FC859}")
			oContext = ThisApplication.TransientObjects.CreateTranslationContext
			oContext.Type = IOMechanismEnum.kFileBrowseIOMechanism
			oOptions = ThisApplication.TransientObjects.CreateNameValueMap
			oDataMedium = ThisApplication.TransientObjects.CreateDataMedium

			If oSTLAddIn.HasSaveCopyAsOptions(oDataMedium, oContext, oOptions) Then
				oOptions.Value("ExportUnits") = 5 
					'INCH = 2
					'FOOT = 3
					'CENTIMETER = 4
					'MILLIMETER = 5
					'METER = 6
					'MICRON = 7
				oOptions.Value("Resolution") = 0
					'HIGH = 0
					'MEDIUM = 1
					'LOW = 2
					'CUSTOM = 3 
					'BREP = 4
				oOptions.Value("ExportFileStructure") = 0
					'ONE FILE = 0
					'ONE FILE PER PART INSTANCE = 1 
			End If
			
			oDataMedium.FileName = oPath & "\" & oFileName & ".stl"
			msgbox(oDataMedium.FileName)

			'Publish document
			Try 
				oSTLAddIn.SaveCopyAs(oDoc, oContext, oOptions, oDataMedium)
			Catch
				MessageBox.Show("There was an error saving the file.  Please make sure that the location " & oPath & " is available.  ", "Network access error", MessageBoxButtons.OK, MessageBoxIcon.Error)
			End Try
		Else
		
			MessageBox.Show("This command can only be used in an Assembly or Part.")
			
		End If
	Else
	
		MessageBox.Show("File must be saved to continue.", "File Not Saved",MessageBoxButtons.OK,MessageBoxIcon.Error)

	End If
End Sub
