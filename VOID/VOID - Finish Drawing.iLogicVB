Dim oDoc As DrawingDocument = ThisApplication.ActiveEditDocument
Dim oCommandMgr As CommandManager = ThisApplication.CommandManager
Dim oRefDocs As DocumentsEnumerator = oDoc.AllReferencedDocuments
Dim oRefDoc As Document = oRefDocs.Item(1)
Dim makeDxf As Boolean = True

invDesignInfo = oRefDoc.PropertySets.Item("Design Tracking Properties")

'DateProp = invDesignInfo.Item("Creation Time")

'DateProp.Value = DateString

oCommandMgr.ControlDefinitions.Item("UpdateCopiedModeliPropertiesCmd").Execute2(True)

If oRefDoc.DocumentType = kAssemblyDocumentObject Then
	makeDXF = False
End If

makeDxf = InputRadioBox("Generate DXF?", "Yes", "No", makeDxf, "iLogic")

If makeDxf = True Then
	iLogicVb.RunExternalRule("Export and Attach DXF")
End If

oDoc.Save

oCommandMgr.ControlDefinitions.Item("VaultCheckinTop").Execute

ThisApplication.ActiveDocument.Close(True)
