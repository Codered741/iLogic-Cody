Sub Main()
	'Declarations
	Dim oDoc As Document = ThisApplication.ActiveEditDocument
	
	Dim VOIDMtls As New List(Of String)
	
	VOIDMtls.Add("6mm (1/4in) FINNISH BIRCH PLYWOOD")
	VOIDMtls.Add("12mm (1/2in) FINNISH BIRCH PLYWOOD")
	VOIDMtls.Add("24mm (1in) FINNISH BIRCH PLYWOOD")
	VOIDMtls.Add("6mm (1/4in) and 12mm (1/2in) FINNISH BIRCH PLYWOOD")
	VOIDMtls.Add("12mm (1/2in) FINNISH BIRCH PLYWOOD AND STEEL TUBE")
	VOIDMtls.Add("24mm (1in) FINNISH BIRCH PLYWOOD AND 4mm BLACK RUBBER")
	VOIDMtls.Add("14GA ASTM A1011 Steel")
	
	Dim oCommandMgr As CommandManager = ThisApplication.CommandManager
	oCommandMgr.ControlDefinitions.Item("VaultCheckout").Execute 'Check out file
	
	iLogicVb.RunExternalRule("Smart Part Property Add")
	
	'Autofill
	iLogicVb.RunExternalRule("Smart Part Property Add")
	iProperties.Value("Custom", "DETAILER") = "Cody Redding"
	iProperties.Value("Project", "Designer") = "Cody Redding"

	If iProperties.Value("Project", "Revision Number") = "N/A" OrElse iProperties.Value("Project", "Revision Number") = "N\A"
		iProperties.Value("Project", "Revision Number") = "0"
	End If

	Parameter("MB") = True

	'Add a select case for the projects you are working on.  pull the list from an excel document.  
	'promt to select from initial list, then import a new list based on that selection.  The selection should be the sheet name containing the options for that job. 

	If isPrt(oDoc) Then
		
		MtlChoice = InputListBox("Select Material", VOIDMtls, VOIDMtls(1), "Part Material", "Select One")
		iProperties.Value("Custom", "MATERIAL DESCRIPTION") = MtlChoice
		
		
		If MtlChoice.ToLower.Contains("plywood") Then
			iProperties.Material= "Plywood, Finish"
			'iProperties.PartColor = "Paint Iron Grey (RAL 7011)"
		Else If MtlChoice.Contains("Steel")
			iProperties.Material = "Steel, Mild"
			'iProperties.PartColor = "Powdercoat Iron Grey (RAL 7011)"
		End If
		
		addOPParam = False
		
	End If
	
	If isAsm(oDoc) Then
		iProperties.Value("Custom", "MATERIAL DESCRIPTION") = "ASSEMBLY"
		addOPParam = True
	End If
	
	
	iProperties.Value("Status", "Checked By") = "Shannon Nickerson"
	Parameter("VendorSupplyMtl") = True
	
	If iProperties.Value("Project", "Description") = "" OrElse iProperties.Value("Project", "Description") = "Standard Assembly File (in)" Then
		Desc = InputBox("Enter Part Description", "iLogic")
		iProperties.Value("Project", "Description") = "VOID V3 " & Desc
	End If
	
	addOPParam = InputRadioBox("Add OS Turnkey OP?", "Yes", "No", addOPParam, Title := "Inventor Rules!")

	If addOPParam Then
		Parameter("OP1") = "OP038:OS - Turnkey Fabrication~"
	End If

	Dim NoteOptions(0 To 10) As String
	
	NoteOptions(0) = "Texture"
	NoteOptions(1) = "No Texture"
	NoteOptions(2) = "Flat w/ Texture"
	NoteOptions(3) = "Deck Parts"
	NoteOptions(4) = "Column"
	NoteOptions(5) = "Wall Panel"
	NoteOptions(6) = "Wall Assembly"
	NoteOptions(7) = "Mounting Panel"
	NoteOptions(8) = "None"
	NoteOptions(9) = "Jig"
	NoteOptions(10) = "Raw w/ FlameStop"
	
	addNotes = InputListBox("Select Note Type", NoteOptions, NoteOptions(10), "Note Types", "Select One")

	If addNotes  = "Texture" Then
		iProperties.Value("Summary", "Comments") = "NOTES" & vbCrLf & _
					"  - APPLY FLAMESTOP II ACCORDING TO MANUFACTURERS INSTRUCTION" & vbCrLf & _
					"  - APPLY TEXTURE ACCORDING TO INCLUDED PROCEDURE"
					iProperties.PartColor = "Paint Iron Grey (RAL 7011)"
	Else If addNotes = "No Texture"
		iProperties.Value("Summary", "Comments") = "NOTES" & vbCrLf & _
					"  - APPLY FLAMESTOP II ACCORDING TO MANUFACTURERS INSTRUCTION"
					iProperties.PartColor = "Paint Iron Grey (RAL 7011)"
	Else If addNotes = "Flat w/ Texture"
		iProperties.Value("Summary", "Comments") = "NOTES" & vbCrLf & _
					"  - ASSEMBLE PARTS USING WOOD GLUE AND STAPLES" & vbCrLf & _
					"  - STAPLE THROUGH STILES INTO RAILS FROM SIDES" & vbCrLf & _
					"  - STAPLE THROUGH TOP/BOTTOM RAILS INTO STILES FROM TOP/BOTTOM" & vbCrLf & _
					"  - STAPLE THROUGH TUBE SUPPORT INTO TOP/BOTTOM RAILS" & vbCrLf & _
					"  - SAND ALL TABS, NO BURRS OR SPLINTERS ALLOWED" & vbCrLf & _
					"  - APPLY 1/4in ROUNDOVER TO ALL EDGES AFTER ASSEMBLY" & vbCrLf & _
					"  - APPLY FLAMESTOP II ACCORDING TO MANUFACTURERS INSTRUCTION" & vbCrLf & _
					"  - PAINT ACCORDING TO INCLUDED PROCEDURE" & vbCrLf & _
					"  - ALL MATERIAL IS 12mm (1/2in) FINNISH BIRCH PLYWOOD, UOS" & vbCrLf & _
					"  - LOCK EXTRUSION IS 1in SQ. STEEL TUBE"
					iProperties.PartColor = "Paint Iron Grey (RAL 7011)"
	Else If addNotes = "Deck Parts"
				iProperties.Value("Summary", "Comments") = "NOTES" & vbCrLf & _
					"  - APPLY FLAMESTOP II ACCORDING TO MANUFACTURERS INSTRUCTION" & vbCrLf & _
					"  - PAINT ALL TOP AND VERTICAL SURFACES BLACK, AFTER RUBBER IS APPLIED"
					iProperties.PartColor = "Paint Iron Grey (RAL 7011)"
	Else If addNotes = "Column"
				iProperties.Value("Summary", "Comments") = "NOTES" & vbCrLf & _
					"  - NOTE DIRECTION OF PIN AND WRENCH HOLES WHEN INSTALLING COFFIN LOCKS" & vbCrLf & _
					"  - USE MEDIUM STRENGTH THREAD LOCKER WHEN INSTALLING ALL FASTENERS" & vbCrLf & _
					"  - WELD AND T-NUTS MUST BE INSTALLED PRIOR TO ASSEMBLING COLUMN" 
					iProperties.PartColor = "Paint Iron Grey (RAL 7011)"
	Else If addNotes = "Wall Assembly"
				iProperties.Value("Summary", "Comments") = "NOTES" & vbCrLf & _
					"  - NOTE DIRECTION OF PIN AND WRENCH HOLES WHEN INSTALLING COFFIN LOCKS" & vbCrLf & _
					"  - USE MEDIUM STRENGTH THREAD LOCKER WHEN INSTALLING ALL FASTENERS" & vbCrLf & _
					"  - WELD AND T-NUTS MUST BE INSTALLED PRIOR TO ASSEMBLING WALL" 
					iProperties.PartColor = "Paint Iron Grey (RAL 7011)"
	Else If addNotes = "None"
		iProperties.Value("Summary", "Comments") = ""
	Else If addNotes = "Mounting Panel"
		iProperties.Value("Summary", "Comments") = "NOTES" & vbCrLf & _
					"  - PINS ARE ORIENTATED OPPOSITE DIRECTION OF ARROW" & vbCrLf & _
					"  - ENSURE THAT HARDWARE IS INSTALLED FLUSH TO BOTTOM FACE" & vbCrLf & _
					"  - PACKAGE 1/4 SHCS HARDWARE AND INSERT NUTS IN BAG, ATTACH TO ASSEMBLY"
					iProperties.PartColor = "Paint Iron Grey (RAL 7011)"
	Else If addNotes = "Wall Panel"				
		iProperties.Value("Summary", "Comments") = "NOTES: " & vbCrLf & _
					"  - ASSEMBLE PARTS USING WOOD GLUE AND STAPLES"& vbCrLf & _
					"  - STAPLE THROUGH STILES INTO RAILS FROM SIDES" & vbCrLf & _
					"  - STAPLE THROUGH TOP/BOTTOM RAILS INTO STILES FROM TOP/BOTTOM" & vbCrLf & _
					"  - STAPLE THROUGH TUBE SUPPORT INTO TOP/BOTTOM RAILS" & vbCrLf & _
					"  - SAND ALL TABS, NO BURRS OR SPLINTERS ALLOWED" & vbCrLf & _
					"  - APPLY 1/4in ROUNDOVER TO ALL EDGES AFTER ASSEMBLY" & vbCrLf & _
					"  - APPLY FLAMESTOP II ACCORDING TO MANUFACTURERS INSTRUCTION" & vbCrLf & _
					"  - PAINT ACCORDING TO INCLUDED PROCEDURE" & vbCrLf & _
					"  - ALL MATERIAL IS 12mm (1/2in) FINNISH BIRCH PLYWOOD, UOS" & vbCrLf & _
					"  - LOCK EXTRUSION IS 1in SQ. STEEL TUBE"
					iProperties.PartColor = "Paint Iron Grey (RAL 7011)"
	Else If addNotes = "Jig"
		iProperties.Value("Summary", "Comments") = "NOTES" & vbCrLf & _
					"  - PART MUST BE FREE OF SPLINTERS OR BURRS.  "
	Else If addNotes = "Raw w/ FlameStop"
		iProperties.Value("Summary", "Comments") = "NOTES" & vbCrLf & _
					"  - APPLY FLAMESTOP II ACCORDING TO MANUFACTURERS INSTRUCTION"
	End If

	'\VOID
	
	
	SetView = MessageBox.Show("Set Front View?", "View Orientation", MessageBoxButtons.YesNo)
	
	Dim oCam As Camera
	oCam = ThisApplication.ActiveView.Camera
	
	If SetView = vbYes Then
		ThisApplication.CommandManager.ControlDefinitions.Item("AppLookAtCmd").Execute2(True)
		
		ThisApplication.ActiveView.SetCurrentAsFront
		
		oCam.Perspective = False
		oCam.ViewOrientationType = 10759 'kIsoTopRightViewOrientation
		oCam.Fit()
		oCam.Apply
		
		ThisApplication.ActiveView.SetCurrentAsHome
		
	Else 
	
		oCam.Perspective = False
		oCam.ViewOrientationType = 10759 'kIsoTopRightViewOrientation
		oCam.Fit()
		oCam.Apply
		
	End If
	
	'Finish Config and Open form for checking
	oDoc.Save2
	iLogicVb.RunExternalRule("Smart Part Config")
	'iLogicForm.ShowGlobal("Smart Part Config")
	iLogicVb.RunExternalRule("AutoDraw")
End Sub

Function isPrt(ThisDoc As Document) As Boolean

	Debug.Print (ThisDoc.DocumentType)

	If ThisDoc.DocumentType = kPartDocumentObject Then

		isPrt = True
		
	Else

		isPrt = False
		
	End If

End Function

Function isAsm(ThisDoc As Document) As Boolean

	Debug.Print (ThisDoc.DocumentType)

	If ThisDoc.DocumentType = kAssemblyDocumentObject Then

		isAsm = True
		
	Else

		isAsm = False
		
	End If

End Function
