Sub Main()

	Dim cmbDesigners as New List(of String)
	
	cmbDesigners = ReadTXT("C:\Dropbox\Cody\Github\iLogic\2 In Development\Props_Designers.txt")
	
	If cmbDesigners.Count > 0 Then
		response = inputListBox("Please Select", cmbDesigners, cmbDesigners(1))
		MsgBox(response)
	Else 
		MsgBox("nope")
	End If
	
End Sub

Function ReadTXT(InputFile as String) As List(of String)
	Dim RawList() as String
	RawList = IO.File.ReadAllLines(InputFile)
	
	Dim List as New ArrayList()
	
	For i as Integer = 0 To RawList.GetUpperBound(0)
		List.Add(RawList(i))
	Next
	
	Dim TempList as New List(of String)
	
	For n = 0 To List.Count - 1
		If List.Item(n).ToString.Substring(0, 1) = "*" Then
			'Do Nothing
		Else 
			TempList.Add(List.Item(n).ToString)
		End If
	Next
	
	ReadTXT = TempList
	
	Return ReadTXT

End Function
