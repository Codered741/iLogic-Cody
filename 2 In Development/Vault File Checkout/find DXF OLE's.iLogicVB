'OLE Ref Finder
'test program

Dim oDoc As Document = ThisApplication.ActiveEditDocument
Dim oRefOLE As ReferencedOLEFileDescriptors = oDoc.ReferencedOLEFileDescriptors
Dim oCommandMgr As CommandManager = ThisApplication.CommandManager
Dim lDXF as New List(of String)

For Each oRef In oRefOLE 

	If oRef.OLEDocumentType = 3331 AndAlso oRef.FullFileName.Contains(".dxf") Then
		lDXF.Add(oRef.FullFileName)
		'oCommandMgr.ControlDefinitions.Item("VaultGetCheckout").Execute
	End If
Next


If lDXF.Count > 0 Then
	MsgBox("Found " & lDXF.Count & " files.  ")
	'For Each dxf in lDXF 
	'	MsgBox(dxf)
	'Next 
Else 
	MsgBox("None.  ")
End If
