'Material Description Generator
'Cody Redding 20171115

'STATUS: In Development

Dim Shape1List (0 to 3) as String
	ShapeList1(0) = "Tube"
	ShapeList1(1) = "Bar"
	ShapeList1(2) = "Beam"
	ShapeList1(3) = "Pipe"

Dim TubeType(0 to 3) As String
	TubeType(0) = "Round"
	TubeType(1) = "Square"
	TubeType(2) = "Rectangular"
	TubeType(3) = "Hexagonal"

Dim BarType(0 to 3)	As String
	BarType(0) = "Round"
	BarType(1) = "Square"
	BarType(2) = "Rectangular"
	BarType(3) = "Hexagonal"
	
Dim BeamType (0 to 2) as String
	BeamType(0) = "W"
	BeamType(1) = "S"
	BeamType(2) = "C"
