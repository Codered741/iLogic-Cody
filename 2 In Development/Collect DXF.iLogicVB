'Collect, Zip?, and Attach DXF's to Drawing
Imports System.IO
Imports System.IO.Path
Imports System.Collections
Imports My.Computer.FileSystem

Sub Main()

	Dim oDoc as Document = ThisApplication.ActiveDocument
	
	If isDwg(oDoc) = False AndAlso isAsm(oDoc) = False
		MsgBox("Please run from an Assembly or Drawing")
		Return
	End If

	Dim collectFolder As String = FilePath(oDoc.FullFileName) & BaseFilename(oDoc.FullFileName) & " DXF " & Now.ToString("yyyyMMddHHmm") & "\"
	MsgBox(collectFolder)
	
	'If System.IO.Directory.Exists(collectFolder) Then
		'System.IO.Directory.Delete(collectFolder, True)
	'End If
	
	Dim oAppend As System.IO.StreamWriter
	Dim oFile As String = "C:\_vaultWIP\Designs\dbug.log"
	
	'Try
		oAppend = IO.File.AppendText(oFile)
	'Catch
		noWrite = True
	'End Try
	
	If noWrite = False Then
		oAppend.WriteLine(ThisApplication.UserName & "," & DateTime.Now.ToString("G") & "," & DocumentFileNameExt(oDoc))
	End If
	
	Dim oRefDocs as DocumentsEnumerator = oDoc.AllReferencedDocuments
	Dim copiedFileName As String
	
	Dim RefDwgFullFileName As String
	Dim RefDwgDocFileName As String 
	Dim RefDwgBaseFileName As String
	
	Dim RefDwgFullFileNamePN As String
	Dim RefDwgDocFileNamePN As String
	Dim RefDwgBaseFileNamePN As String
	
	Dim iProps as PropertySet
	Dim RefPN
	
	For Each oRefDoc in oRefDocs
		iProps = oRefDoc.PropertySets.Item("Design Tracking Properties")
		RefPN = iProps.Item("Part Number")
		
		oAppend.Write(oRefDoc.FullFileName & ",")
		
		RefDwgFullFileName = FindDrawingFile(oRefDoc)
		oAppend.Write(RefDwgFullFileName & ",")
		
		If RefDwgFullFileName.Length > 5 Then 
			RefDwgDocFileName = DocumentFileName(RefDwgFullFileName)
			RefDwgBaseFileName = BaseFilename(RefDwgFullFileName)
		End If
		
		RefDwgFullFileNamePN = FindDrawingFilePN(oRefDoc)
		oAppend.Write(RefDwgFullFileNamePN & ",")
		
		If RefDwgFullFileNamePN.Length > 5 Then	
			RefDwgDocFileNamePN = DocumentFileName(RefDwgFullFileNamePN)
			RefDwgBaseFileNamePN = BaseFilename(RefDwgFullFileNamePN)
		End If
		
		If RefDwgFullFileName <> "" Then
			'look for files with the same file name as ref doc, in the project location
			FileNameDXF = RefDwgDocFileName & ".dxf"
			oAppend.Write(FileNameDXF & ",")
			copiedFileName = collectFolder & RefDwgBaseFileName & ".dxf"
			
			DoCollect(FileNameDXF,copiedFileName, collectFolder)
			
			'look for drawing file with the same file name as the ref doc, in the project location, page 1-10
			For i = 1 To 10 'search for pages 1-10
				FileNameDXF = RefDwgDocFileNamePN & " p" & i & ".dxf"
				oAppend.Write(FileNameDXF & ",")
				copiedFileName = collectFolder & RefDwgBaseFileName & " p" & i & ".dxf"
				
				DoCollect(FileNameDXF,copiedFileName, collectFolder)
				
			Next 
		End If
		
		If RefDwgFullFileNamePN <> "" Then
			'look for files with the part number of the ref doc, in the project location
			FileNameDXF =  Left(RefDwgDocFileNamePN, RefDwgDocFileNamePN.Length - RefPN.Value.Length) & ".dxf"
			oAppend.Write(FileNameDXF & ",")
			copiedFileName = collectFolder & RefDwgBaseFileNamePN &  ".dxf"
			
			DoCollect(FileNameDXF, copiedFileName, collectFolder)
					
			'look for files with the part number of the ref doc, in the project location, page 1-10
			For i = 1 To 10 'search for pages 1-10 by part number
				FileNameDXF = Left(RefDwgDocFileNamePN, RefDwgDocFileNamePN.Length - RefPN.Value.Length) & " p" & i & ".dxf"
				oAppend.Write(FileNameDXF)
				copiedFileName = collectFolder & RefDwgBaseFileNamePN & " p" & i & ".dxf"
				
				DoCollect(FileNameDXF,copiedFileName, collectFolder)
				
			Next
		End If
		
		oAppend.WriteLine("")
		
	Next
	
	If System.IO.Directory.Exists(collectFolder) Then
		Process.Start(collectFolder)
	End If
	
	oAppend.Flush()
	oAppend.Close()
	
	MsgBox("Done")
	
End Sub 'Main

Sub DoCollect(FileNameDXF as String, copiedFileName As String, collectFolder As String)
	If System.IO.File.Exists(FileNameDXF) Then 'search for single page drawings
		System.IO.Directory.CreateDirectory(collectFolder)
		My.Computer.FileSystem.CopyFile(FileNameDXF, copiedFileName, Microsoft.VisualBasic.FileIO.UIOption.AllDialogs, Microsoft.VisualBasic.FileIO.UICancelOption.DoNothing)
	End If
End Sub 'DoCollect

Function FindDrawingFile(PartOrAssemblyDoc As Document)
    Dim fullFilename As String
    fullFilename = PartOrAssemblyDoc.fullFilename
   
    ' Extract the path from the full filename.
    Dim path As String
    path = "C:\_vaultWIP\Designs"
   
    ' Extract the filename from the full filename.
    Dim filename As String
    filename = Right$(fullFilename, Len(fullFilename) - InStrRev(fullFilename, "\"))
   
    ' Replace the extension with "dwg"
    filename = Left$(filename, InStrRev(filename, ".")) & "dwg"
   
    ' Find if the drawing exists.
    Dim drawingFilename As String
    drawingFilename = ThisApplication.DesignProjectManager.ResolveFile(path, filename)
   
    ' Check the result.
    If drawingFilename = "" Then
        ' Try again with idw extension.
        filename = Left$(filename, InStrRev(filename, ".")) & "idw"
       
        ' Find if the drawing exists.
        drawingFilename = ThisApplication.DesignProjectManager.ResolveFile(path, filename)
   
        ' Return the result.
        If drawingFilename <> "" Then
            FindDrawingFile = drawingFilename
        Else
            FindDrawingFile = ""
        End If
    Else
        ' Return the result.
        FindDrawingFile = drawingFilename
    End If
End Function 'FindDrawingFile

Function FindDrawingFilePN(PartOrAssemblyDoc As Document)
    Dim fullFilenamePN As String
    fullFilenamePN = PartOrAssemblyDoc.fullFilename
   
    ' Extract the path from the full filename.
    Dim path As String = "C:\_vaultWIP\Designs"
    'path = Left$(fullFilenamePN, InStrRev(fullFilenamePN, "\"))
   
	Dim iProps as PropertySet = PartOrAssemblyDoc.PropertySets.Item("Design Tracking Properties")
	Dim pn = iProps.Item("Part Number")
	
    Dim filename As String = pn.Value
    'filename = Right$(fullFilenamePN, Len(fullFilenamePN) - InStrRev(fullFilenamePN, "\"))
   
    ' Replace the extension with "dwg"
    filename = filename & ".dwg"
   
    ' Find if the drawing exists.
    Dim drawingFilename As String
    drawingFilename = ThisApplication.DesignProjectManager.ResolveFile(path, filename)
   
    ' Check the result.
    If drawingFilename = "" Then
        ' Try again with idw extension.
        filename = filename & "idw"
       
        ' Find if the drawing exists.
        drawingFilename = ThisApplication.DesignProjectManager.ResolveFile(path, filename)
   
        ' Return the result.
        If drawingFilename <> "" Then
            Return drawingFilename
        Else
            Return ""
        End If
    Else
        ' Return the result.
         Return drawingFilename
    End If
End Function 'FindDrawingFilePN

Function isDwg(ThisDoc as Document) As Boolean
	Debug.Print (ThisDoc.DocumentType)
	If ThisDoc.DocumentType = kDrawingDocumentObject
		isDwg = True
	Else 
		isDwg = False
	End If
End Function 'isDwg

Function DocumentFileName(Doc As String) As String
	DocumentFileName = Left(Doc, Doc.Length - 4)
	'MsgBox(DocumentFileName)
End Function 'DocumentFileName

Function isAsm(ThisDoc As Document) As Boolean
	Debug.Print (ThisDoc.DocumentType)
	If ThisDoc.DocumentType = kAssemblyDocumentObject Then
		isAsm = True
	Else
		isAsm = False
	End If
End Function 'isAsm

Function BaseFilename(ByVal fullFilename As String) As String
    Dim temp As String
    temp = Right(fullFilename, Len(fullFilename) - InStrRev(fullFilename, "\"))
    BaseFilename = Left(temp, InStrRev(temp, ".") - 1)
End Function 'BaseFilename

Function FilePath(ByVal fullFilename As String) As String
    FilePath = Left(fullFilename, InStrRev(fullFilename, "\"))
End Function 'FilePath

Function DocumentFileNameExt(Doc as Document) As String
	DocumentFileNameExt = IO.Path.GetFileName(Doc.FullFileName)
End Function 'DocumentFileNameExt
