Sub Main()
	GetPerimeter
	
End Sub

Public Sub GetPerimeter()

    '  a reference to the part component definition.
    ' This assumes that a part document is active.
    Dim oCompDef As PartComponentDefinition
    oCompDef = ThisApplication.ActiveDocument.ComponentDefinition
	
    ' Get the first face of the model.  This sample assumes a simple
    ' model where at least the first face is a plane.  (A box is a good
    ' test case.)
	Dim oFace As Face
    oFace = ThisApplication.CommandManager.Pick(SelectionFilterEnum.kPartFacePlanarFilter, "Select bottom face")
    ' Get one of the edges of the face to use as the sketch x-axis.
    Dim oEdge As Edge
    oEdge = oFace.Edges.Item(2)
    
    ' Get the start vertex of the edge to use as the origin of the sketch.
    Dim oVertex As Vertex
    oVertex = oEdge.StartVertex

    ' Create a new sketch.  This last argument is  to true to cause the
    ' creation of sketch geometry from the edges of the face.
    Dim oSketch As PlanarSketch
    oSketch = oCompDef.Sketches.AddWithOrientation(oFace, oEdge, True, True, oVertex, True)
    
    ' Change the name.
    oSketch.Name = "Router Estimate"
    
	Dim oProfile As Profile
	oProfile = oSketch.Profiles.AddForSolid

	Dim oRegionProps As RegionProperties
    oRegionProps = oProfile.RegionProperties
	
	oRegionProps.Accuracy = AccuracyEnum.kMedium

	MsgBox(Round(oRegionProps.Perimeter, 2))
	
	oSketch.Delete
	
End Sub
