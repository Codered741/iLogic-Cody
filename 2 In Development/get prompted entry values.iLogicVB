'AUTHOR: Cody Redding 
'CONTACT: Codered741@gmail.com
'LAST MODIFIED: 20170825
'STATUS: In Testing
'LICENSE: Free to redistribute without authorization

'function returns value of prompted entry on drawing sheet
Sub Main()
	Dim oDoc as Document = ThisApplication.ActiveDocument
	Dim oSheets as Sheets = oDoc.Sheets
	Dim oSheet as Sheet
	For Each oSheet In oSheets 
	
		IvGetPromptedValue(oTb, "Page Title Prompt")
		
	Next
End Sub

Public Function IvGetPromptedValue(ByRef oTbl As Inventor.TitleBlock, sPromptName As String) As String
	'get value of specified prompted property from titleblock and return it
	'with Function. If property can't be found return "-1"
	'
	'references:
	'mXML.ParseXML

	Dim oTextBoxes As Inventor.TextBoxes
	Dim lBox As Long

	'get textboxes of titleblock
	oTextBoxes = oTbl.Definition.Sketch.TextBoxes

	'iterate through text boxes and find value
	For lBox = oTextBoxes.Count To 1 Step -1
		If Left(GetFormattedText(oTextBoxes(lBox)), 8) = "" Then
			Dim sValue As String
			sValue = ParseXML(oTextBoxes(lBox).FormattedText, "Prompt")

			If UCase(sValue) = UCase(sPromptName) Then
				IvGetPromptedValue = oTbl.GetResultText(oTextBoxes(lBox))
				Exit Function
			End If
		End If
	Next

	IvGetPromptedValue = "-1"
End Function


Private Function GetFormattedText(ByRef oTextBox As Inventor.TextBox) As String
	'get value of formatted text property. If error return error string
	On Error Resume Next

	GetFormattedText = oTextBox.FormattedText

	If Err Then
		Err.Clear
		GetFormattedText = ""
	End If
End Function
