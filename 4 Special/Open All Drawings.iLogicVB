Imports System.IO
'Imports System.IO.Path
'Imports System.Collections
'Imports My.Computer.FileSystem


'Type queueType = Type.GetTypeFromProgID("PDFCreator.JobQueue")
'Activator.CreateInstance(queueType)

' AddReference "C:\Program Files\PDFCreator\PDFCreator.ComWrapper.dll"
' Imports pdfforge.PDFCreator.UI.ComWrapper

Sub Main()
	' Dim VaultAddin As Inventor.ApplicationAddIn = ThisApplication.ApplicationAddIns.ItemById("{48B682BC-42E6-4953-84C5-3D253B52E77B}")
	' VaultAddin.Deactivate()
	

	
	
	Try 
		Dim oDoc as Document = ThisApplication.ActiveDocument
		
		'check if active document is an assembly
		If isAsm(oDoc) = False
			MsgBox("Please run from an Assembly")
			Return
		End If
		
		'write to iLogic Log
		' SharedVariable("LogVar") = "Batch Plot to PDFCreator"
		' iLogicVB.RunExternalRule("Write SV to Log.iLogicVB")
		
		'create access to Batch Plot log
		' Dim oAppend As System.IO.StreamWriter
		' Dim oFile As String = "Z:\Inventor Data\BPLog.log"
		
		' 'try getting access to log, disable CSV output if access cannot be gained.  
		' Try
			' oAppend = IO.File.AppendText(oFile)
		' Catch
			' noWrite = True
		' End Try
		
		
		'Start Stream output, user name and date stamp
		' If Not noWrite = True Then
			' oAppend.WriteLine("/////////////////////BATCH EXPORT PDF/////////////////////")
			' oAppend.WriteLine(ThisApplication.UserName & "," & DateTime.Now.ToString("G") & "," & oDoc.FullFileName)
		' End If
		
		'Declare variables
		Dim oRefDocs as DocumentsEnumerator = oDoc.AllReferencedDocuments
		Dim copiedFileName As String
		Dim RefDwgFullFileName As String
		Dim iProps as PropertySet
		Dim RefPN
		Dim PrinterName as String = "PDFCreator"
		Dim lstDrawings as New List(of String)
		Dim lstModels as New List(of String)
		
		Dim oProgressBar as Inventor.ProgressBar
		Dim DocCount = oRefDocs.Count
		oProgressBar = ThisApplication.CreateProgressBar(False, DocCount, "Finding Drawings...")
		
		'Find drawing of current document and print if found
		'Get part number property of the filename
		iProps = oDoc.PropertySets.Item("Design Tracking Properties")
		RefPN = iProps.Item("Part Number")
		
		'write to log
		'oAppend.Write(oDoc.FullFileName & ",")

		'Attempt to find a drawing file of the same name as the assembly doc
		RefDwgFullFileName = FindDrawingFilePN(oDoc)
		
		oProgressBar.Message = "Checking for drawing of " & oDoc.FullFileName
		oProgressBar.UpdateProgress
		
		If RefDwgFullFileName.Length > 5 Then 
		
			lstDrawings.Add(RefDwgFullFileName)
			lstModels.Add(oDoc.FullFileName)
			
		End If
		
		For Each oRefDoc as Document In oDoc.AllReferencedDocuments
			'Get part number property of the filename
			iProps = oRefDoc.PropertySets.Item("Design Tracking Properties")
			RefPN = iProps.Item("Part Number")
			
			oProgressBar.Message = "Checking for drawing of " & oRefDoc.FullFileName
			oProgressBar.UpdateProgress
			
			'write to log
			'oAppend.Write(oRefDoc.FullFileName & ",")

			'Attempt to find a drawing file of the same name as the model doc
			RefDwgFullFileName = FindDrawingFilePN(oRefDoc)
				
			If RefDwgFullFileName.Length > 5 Then 
				
				lstDrawings.Add(RefDwgFullFileName)
				lstModels.Add(oRefDoc.FullFileName)

			End If
			
		Next
		
		oProgressBar.Close
		
		oProgressBar = ThisApplication.CreateProgressBar(False, lstDrawings.Count, "Opening Files...")
		For i = 1 To lstDrawings.Count
			ThisApplication.Documents.Open(lstDrawings(i), True)
			ThisApplication.Documents.Open(lstModels(i), True)
			'oPro
		Next
		
		'MergePrintDwgs(oDoc.FullFileName, lstDrawings)
		
	Catch Ex as Exception
	
		MsgBox("Original error: " & Ex.Message)
		
	Finally 
	
		' VaultAddin.Activate
		
	End Try
	
End Sub 'Main

Private Sub MergePrintDwgs(strFilePath as String, lstDwgsPrint as List(of String))
	
	Dim PDFCreatorQueue As Queue = New Queue
	Dim job As Object
	Dim fullPath As String
	
	Dim oProgressBar As Inventor.ProgressBar = ThisApplication.CreateProgressBar(False, lstDwgsPrint.Count, "Printing Drawings...")

	Try

		fullPath = DocumentFileName(strFilePath) 'Path.Combine(Path.GetTempPath, Path.GetTempFileName)
		
		'MsgBox("Initializing PDFCreator queue...")
		PDFCreatorQueue.Initialize()
		
		'setup options for open
		Dim oOptions as NameValueMap = ThisApplication.TransientObjects.CreateNameValueMap
		oOptions.Value("DeferUpdates") = True
		oOptions.Value("FastOpen") = True
		
		'MsgBox("Printing windows test page...")
		For Each DwgName as String In lstDwgsPrint
		
			oProgressBar.Message = "Printing drawing file: " & DwgName
			oProgressBar.UpdateProgress
			ThisApplication.Documents.OpenWithOptions(DwgName, oOptions, True)
			DwgPrint("PDFCreator")
			ThisApplication.ActiveDocument.Close(True)
			
		Next

		If Not PDFCreatorQueue.WaitForJobs(lstDwgsPrint.Count, lstDwgsPrint.Count * 10) Then
			MsgBox("The print job did not reach the queue within the allotted time.  ")
		Else
		
			PDFCreatorQueue.MergeAllJobs
			'MsgBox("Currently there are " & PDFCreatorQueue.Count & " job(s) in the queue")
			'MsgBox("Getting job instance")
			job = PDFCreatorQueue.NextJob

			job.SetProfileByGuid("DefaultGuid")

			'MsgBox("Converting under ""DefaultGuid"" conversion profile")
			job.ConvertTo(fullPath)

			If (Not job.IsFinished Or Not job.IsSuccessful) Then
				MsgBox("Could not convert the file: " & fullPath)
			Else
				'MsgBox("Job finished successfully")
			End If
		End If
		
	Catch Ex As Exception
	
		MessageBox.Show("Original error: " & Ex.Message)
		
	Finally
	
		'MsgBox("Releasing the queue object")
		PDFCreatorQueue.ReleaseCom()
		oProgressBar.Close
		
	End Try
	
	ThisDoc.Launch(fullPath & ".pdf")
	
End Sub

Function FindDrawingFilePN(PartOrAssemblyDoc As Document)
    Dim fullFilenamePN As String
    fullFilenamePN = PartOrAssemblyDoc.fullFilename
   
    ' Extract the path from the full filename.
    Dim path As String = ThisApplication.DesignProjectManager.ActiveDesignProject.WorkspacePath
    'path = Left$(fullFilenamePN, InStrRev(fullFilenamePN, "\"))
   
	Dim iProps as PropertySet = PartOrAssemblyDoc.PropertySets.Item("Design Tracking Properties")
	Dim pn = iProps.Item("Part Number")
	
    Dim filename As String = pn.Value
    'filename = Right$(fullFilenamePN, Len(fullFilenamePN) - InStrRev(fullFilenamePN, "\"))
   
    ' Replace the extension with "dwg"
    filename = filename & ".dwg"
   
    ' Find if the drawing exists.
    Dim drawingFilename As String
    drawingFilename = ThisApplication.DesignProjectManager.ResolveFile(path, filename)
   
    ' Check the result.
    If drawingFilename = "" Then
        ' Try again with idw extension.
        filename = filename & "idw"
       
        ' Find if the drawing exists.
        drawingFilename = ThisApplication.DesignProjectManager.ResolveFile(path, filename)
   
        ' Return the result.
        If drawingFilename <> "" Then
            Return drawingFilename
        Else
            Return ""
        End If
    Else
        ' Return the result.
         Return drawingFilename
    End If
End Function 'FindDrawingFilePN

Private Sub DwgPrint(PrinterName as String)
	Dim oPrintMgr As DrawingPrintManager = ThisApplication.ActiveDocument.PrintManager
	' Get the name of the printer that will be used.
	oPrintMgr.Printer = PrinterName
	
	' Set to print in color.
	oPrintMgr.ColorMode = 13313 'kPrintColorPalette
	
	' Set to print one copies.
	oPrintMgr.NumberOfCopies = 1
	
	' Set to print using landscape orientation.
	oPrintMgr.Orientation = 13570
		'13570 'kLandscapeOrientation
		'13569 'kPortraitOrientation
	
	' Set the paper size.
	oPrintMgr.PaperSize = 14338
		'14338 'kPaperSize11x17
	
	' Set to print all sheets.
	oPrintMgr.PrintRange = 14082 'kPrintAllSheets
	
	' Set to print full scale.
	oPrintMgr.ScaleMode = 13825 'kPrintFullScale
	
	' Submit the print.
	oPrintMgr.SubmitPrint
End Sub 'DwgPrint

Private Sub printTestFile()
	Dim ShellObj As Object

	ShellObj = CreateObject("Shell.Application")
	ShellObj.ShellExecute("RUNDLL32.exe", "PRINTUI.DLL,PrintUIEntry /k /n ""PDFCreator""", "", "open", 1)
End Sub

Function DocumentFileName(Doc As String) As String
	DocumentFileName = Left(Doc, Doc.Length - 4)
	'MsgBox(DocumentFileName)
End Function 'DocumentFileName

Function isAsm(ThisDoc As Document) As Boolean
	Debug.Print (ThisDoc.DocumentType)
	If ThisDoc.DocumentType = kAssemblyDocumentObject Then
		isAsm = True
	Else
		isAsm = False
	End If
End Function 'isAsm
