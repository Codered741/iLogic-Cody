Sub Main()

	Dim oDoc as Document = ThisApplication.ActiveDocument
	Dim userProps as PropertySet = oDoc.PropertySets.Item("Inventor User Defined Properties")
	Dim pOPS = userProps.Item("OPS")
	Dim pMtlRem = userProps.Item("MATERIAL REMOVED")
	Dim pHoles = userProps.Item("Holes")
	Dim pHolesTap = userProps.Item("HolesTapped")
	Dim pEdges = userProps.Item("Edge Count")
	Dim pMilledFaceCount = userProps.Item("MilledFaceCount")
	Dim pPerim = userProps.Item("Perimeter")
	Dim pMaterial = userProps.Item("MATERIAL DESCRIPTION")
		
	' pMilledFaceCount.Value = 0
	' pPerim.Value = 0

	'Get Machined Sides
	pMilledFaceCount.Value = InputBox("Please enter the number of Machined Sides (1-6)", "Mill OP Detected", "0")

	MsgBox("Please select the bottom router face.  ", Title := "Router OP detected")
	pPerim.Value = GetPerimeter(oDoc)

	Dim MillingTime As Double
	Dim DrillTime As Double
	Dim TapTime As Double
	Dim FlipTime As Double
	Dim RoutingTime As Double
	Dim SetupTime As Double
	Dim ProgramTime As Double
	Dim ComplexMult As Double
	Dim MillPerPart As Double
	Dim MillSetup As Double

	ComplexMult = ComplexityModifier(pEdges.Value)

	'Estimate Time to remove material, defaults to steel value unless aluminum is detected.  
	If pMaterial.Value.Contains("Aluminum") AndAlso pMilledFaceCount.Value > 0 Then
		MillingTime	= (pMtlRem.Value / 0.3616)*ComplexMult
	Else 'If pMaterial.Value.Contains("Steel") 
		MillingTime = (pMtlRem.Value / 0.1448)*ComplexMult
	End If

	If pPerim.Value > 0 Then 
		RoutingTime = Round(pPerim.Value / 100, 2) 'Check this Value
	End If

	DrillTime = pHoles.Value * 30
	TapTime = pHolesTap.Value * 30
	FlipTime = pMilledFaceCount.Value * 30

	SetupTime = pMilledFaceCount.Value * 1800
	ProgramTime = ComplexMult * 600

	If pMilledFaceCount.Value > 0 Then
		MillPerPart = Round((MillingTime + DrillTime + TapTime + FlipTime)/60, 2)
	Else 
		MillPerPart = 0
	End If

	MillSetup = (SetupTime + ProgramTime)/60
	
	If pOPS.Value.Contains("OP011") Then
		MsgBox("Milling Time (per Part): " & MillPerPart & " min" & vbCrLf & _
		"Mill Setup (one time): " & MillSetup & " min")
	End If
	
	If pOPS.Value.Contains("OP010") Then
		MsgBox("Routing Time: " & RoutingTime & " min")
	End If
	
	'MsgBox("Mill Setup (one time): " & MillSetup & " min")
End Sub

Function ComplexityModifier(Count as Integer) As Integer
	Select Case	Count
		Case 1 to 100
			ComplexityModifier = 1.5
		Case 101 to 200
			ComplexityModifier = 1.8
		Case 201 To 300
			ComplexityModifier = 2.1
		Case 301 To 400
			ComplexityModifier = 2.5
		Case 401 To 500
			ComplexityModifier = 2.8
		Case 501 To 600
			ComplexityModifier = 3.4
		Case 601 To 700
			ComplexityModifier = 4
		Case 701 To 800
			ComplexityModifier = 5
		Case 801 To 900
			ComplexityModifier = 6
		CAse 901 To 1000
			ComplexityModifier = 7
		Case 1001 To 1100
			ComplexityModifier = 8
		Case 1101 To 1200
			ComplexityModifier = 8.5
		Case 1201 To 1300
			ComplexityModifier = 9
		Case 1301 To 1400
			ComplexityModifier = 9.5
		Case Count > 1401
			ComplexityModifier = 10
	End Select
End Function
