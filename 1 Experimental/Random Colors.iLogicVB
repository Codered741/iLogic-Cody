Private Sub Main
    UpdateAssyBrowser(ThisDoc.Document)
End Sub

  Private Sub UpdateAssyBrowser(ByVal oDoc As Inventor.Document)
    Dim oAssy As Inventor.AssemblyDocument
    Dim oComp As Inventor.ComponentOccurrence
    Dim oSubDoc As Inventor.Document

    Dim NodeName() As String
    Dim InstNum As String
	
	Randomize()
	
	Dim Red as Byte
	Dim Green As Byte
	Dim Blue As Byte
	
    If oDoc.DocumentType = Inventor.DocumentTypeEnum.kAssemblyDocumentObject Then
      oAssy = CType(oDoc, AssemblyDocument)
	  
	Dim RS as Render Style
	
	For Each oComp In oAssy.ComponentDefinition.Occurrences
        oSubDoc = CType(oComp.Definition.Document, Document)
		'If Left(oComp.Name,7) = "PlyWood" Then
			'If oSubDoc.DocumentType = Inventor.DocumentTypeEnum.kPartDocumentObject Then
				'MessageBox.show("Matching Part file found!")
				
				
				Red = CByte((255 * Rnd()))
				Green = CByte((255 * Rnd()))
				Blue = CByte((255 * Rnd()))
				
				colorName = "RGB(" & Red * "," & Green & "," & Blue & ")"
				
				CreateSimpleColorAppearance(oDoc, colorName, Red, Green, Blue)
				
				Component.Color(oComp.Name) = colorName
				
				oComp.appearance = color
			'End If
		'End If
        'If oSubDoc.DocumentType = Inventor.DocumentTypeEnum.kAssemblyDocumentObject Then
        '  Call UpdateAssyBrowser(oSubDoc)
        'End If

      Next oComp
    End If
  End Sub
  
  Public Sub CreateSimpleColorAppearance(doc as Document, colorName as String, red as Byte, green as Byte, blue as Byte)
    ' Dim doc As Document
    ' Set doc = ThisApplication.ActiveDocument
    
    ' Only document appearances can be edited, so that's what's created.
    ' This assumes a part or assembly document is active.
    Dim docAssets As Assets
    docAssets = doc.Assets
    
	colorName = "RGB(" & red * "," & green & "," & blue & ")"
	
    ' Create a new appearance asset.
    Dim appearance As Asset
    appearance = docAssets.Add(kAssetTypeAppearance, "Temp", colorName, colorName)
    
    Dim tobjs As TransientObjects
    tobjs = ThisApplication.TransientObjects


    Dim color As ColorAssetValue
    color = appearance.Item("generic_diffuse")
    color.value = tobjs.CreateColor(red, blue, green)
    
    Dim floatValue As FloatAssetValue
    floatValue = appearance.Item("generic_reflectivity_at_0deg")
    floatValue.value = 0.5
    
    floatValue = appearance.Item("generic_reflectivity_at_90deg")
    floatValue.value = 0.5
End Sub
