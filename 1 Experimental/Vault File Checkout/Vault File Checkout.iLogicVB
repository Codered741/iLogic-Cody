'AUTHOR: Cody Redding 
'CONTACT: Codered741@gmail.com
'LAST MODIFIED: 20171031


'DESCRIPTION: Check out specified file.  

'https://forums.autodesk.com/t5/vault-customization/checking-in-and-out-a-file/m-p/4312060

'NOTE: vault server name and Vault name removed.  

AddReference "C:\Program Files (x86)\Autodesk\Autodesk Vault 2017 SDK\bin\x64\Autodesk.DataManagement.Client.Framework.xml"

Imports System.Drawing
Imports System.Collections
Imports System.ComponentModel
Imports System.Windows.Forms
Imports System.Data
Imports System.Linq

'wB added
Imports System.IO

Imports Autodesk.Connectivity.WebServices
Imports Autodesk.Connectivity.WebServicesTools
Imports VDF = Autodesk.DataManagement.Client.Framework
Dim oVaultServer as String
Dim oVaultName as String


Sub Main()
	'DownloadFiles()
	ReadLogin("C:\Dropbox\Cody\Github\iLogic-Cody\Secrets\TaitVault.txt")
	GetCheckout(oVaultServer, oVaultName)
End Sub

Sub ReadLogin(LoginFile as String)
	Dim oReader as System.IO.StreamReader = New System.IO.StreamReader(LoginFile)
	Dim Raw as String = oReader.ReadLine()
	oReader.Close()
	
	oVaultServer = Right(Raw, InStr(Raw, "|"))
	oVaultName = Left(Raw, InStrRev(Raw, "|"))
End Sub

Public Sub DownloadFiles(fileIters As ICollection(Of VDF.Vault.Currency.Entities.FileIteration))

       ' download individual files to a temp location

       Dim settings As NewVDF.Vault.Settings.AcquireFilesSettings(m_conn)

       settings.LocalPath = NewVDF.Currency.FolderPathAbsolute("c:\temp")

       For Each fileIter AsVDF.Vault.Currency.Entities.FileIteration In fileIters

              settings.AddFileToAcquire(fileIter, VDF.Vault.Settings.AcquireFilesSettings.AcquisitionOption.Download)

       Next

 

       Dim results As VDF.Vault.Results.AcquireFilesResults = m_conn.FileManager.AcquireFiles(settings)

End Sub


Private Sub GetCheckout(oVaultServer as String, oVaultName as String)
	' For demonstration purposes, the information is hard-coded.
	Dim results As VDF.Vault.Results.LogInResult = VDF.Vault.Library.ConnectionManager.LogIn(oVaultServer, oVaultName, "Guest", "Guest", VDF.Vault.Currency.Connections.AuthenticationFlags.Standard, Nothing)

	If Not results.Success Then
		MsgBox("Fail")
		Return
		
	Else If 
		MsgBox("No Fail")
	End If

	Dim connection As VDF.Vault.Currency.Connections.Connection = results.Connection

	' Get the FileIteration 
	Dim oFileIteration As VDF.Vault.Currency.Entities.FileIteration =
									getFileIteration("12345 Testing XXXX.csv", connection)

	'Dim fldrPath As Autodesk.DataManagement.Client.Framework.Currency.FolderPathAbsolute = connection.WorkingFoldersManager.GetWorkingFolder(oFileIteration)
	Dim fldrPath As VDF.Currency.FolderPathAbsolute = New VDF.Currency.FolderPathAbsolute("c:\Temp")
	Dim filePath As String = Path.Combine(fldrPath.ToString(), oFileIteration.EntityName)
	Dim filePathAbs As VDF.Currency.FilePathAbsolute = New VDF.Currency.FilePathAbsolute(filePath)

	'determine if the file exists
	If Not System.IO.File.Exists(filePath) Then
		MessageBox.Show("The file you are attempting to check in does not exist on disk.")
		'Logout
		VDF.Vault.Library.ConnectionManager.LogOut(connection)
		Return
	End If

	If oFileIteration.IsCheckedOut = True Then

		connection.FileManager.CheckinFile(oFileIteration, "wbTesting", False, New ACW.FileAssocParam() {},
																		 Nothing, False, Nothing,
											  ACW.FileClassification.None, False, filePathAbs)

	End If

	'Logout
	VDF.Vault.Library.ConnectionManager.LogOut(connection)
End Sub
