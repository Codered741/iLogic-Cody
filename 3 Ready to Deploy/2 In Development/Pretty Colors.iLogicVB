'highlighter colors
'Runs in an Assembly to give all first level components a random color.  
'Procedure:
' Get all first level components
' Create/Switch to new view rep ("Pretty Colors")
' iterate through the components
'  select all instances
'  generate a random color
'  assign color to instances

Sub Main()
    Dim oAsmDoc As AssemblyDocument = ThisApplication.ActiveDocument
	Dim oAsmDef As AssemblyComponentDefinition = oAsmDoc.ComponentDefinition
	Dim dViewRepMgr As RepresentationsManager = oAsmDef.RepresentationsManager
	Dim dViewReps As DesignViewRepresentations = dViewRepMgr.DesignViewRepresentations
	Dim dMasterViewRep As DesignViewRepresentation = dViewReps.Item(1) 'assume that the first view rep is the master
	Dim vRepName as String = "Pretty Colors" 'name for the new view rep
	Dim dPCViewRep As DesignViewRepresentation = dViewReps.Item(vRepName)
	Dim oOccs as ComponentOccurrencesEnumerator
	
	Try
		dPCViewRep.Activate()
	Catch 
		dMasterViewRep.Activate()
		dViewReps.Add(vRepName)
		dPCViewRep.Activate()
	End Try 
		
    ' Initialize the random number generator and get
    ' the number of render styles defined.
    Randomize
    Dim iColorCount As Long
    iColorCount = oAsmDoc.RenderStyles.Count
	
	If oAsmDoc.AllReferencedDocuments.Count > 30 Then
		uCont = MessageBox.Show("This assembly has a large number of parts.  This operation may take considerable time.  Are you sure you want to continue?", "Inventor", MessageBoxButtons.OKCancel, MessageBoxIcons.Question)
		If uCont = vbCancel Then
			Exit Sub
		End If
	End If
		
	For Each refDoc in oAsmDoc.AllReferencedDocuments
		If refDoc.DocumentType = kPartDocumentObject Then
			oOccs = oAsmDef.Occurrences.AllReferencedOccurrences(refDoc)
			pColor = Int((iColorCount * Rnd) + 1)
			For Each oOcc In oOccs
				oOcc.SetRenderStyle(kOverrideRenderStyle, oAsmDoc.RenderStyles.Item(pColor))
			Next
		End If
	Next
	
End Sub 'Main
