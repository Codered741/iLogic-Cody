'https://forums.autodesk.com/t5/inventor-customization/possible-to-check-all-members-of-factory-for-errors-using-ilogic/m-p/3863094/highlight/true#M43278
sub Main()
	Dim oDoc As Inventor.Document = ThisApplication.ActiveDocument
	Dim currow As Integer
	Dim Max As Integer = 10
	Dim opFactory
	
	InventorVb.DocumentUpdate()
	
	If oDoc.DocumentType = kPartDocumentObject Then
		If oDoc.ComponentDefinition.IsiPartFactory Then
			opFactory = oDoc.ComponentDefinition.iPartFactory
		End if
	Else If oDoc.DocumentType = kAssemblyDocumentObject Then
		If oDoc.ComponentDefinition.IsiAssemblyFactory Then
			opFactory = ThisApplication.ActiveDocument.ComponentDefinition.iAssemblyFactory
		End If
	Else
		MsgBox("Not a factory")
		Exit Sub
	End If
	
	currow = opFactory.DefaultRow.Index
	opFactory.DefaultRow = opFactory.TableRows.Item(1)

	Dim props = ThisApplication.ActiveDocument.PropertySets.Item("Design Tracking Properties")
	Dim pPN = props.Item("Part Number")

	If opFactory.TableRows.Count > Max
		Proceed = MessageBox.Show("This will try to open " & opFactory.TableRows.Count & " files, and may take some time to execute.  Do you want to continue?  ", "Time Warning",MessageBoxButtons.YesNo,MessageBoxIcon.Warning)
	Else
		Proceed = vbYes
	End If

	If Proceed = vbYes
		' Iterate through the rows
		For Each opRow In opFactory.TableRows
			opFactory.DefaultRow=opRow
			
			opRowFile = FindDrawingFileByName(pPN.Value & ".ipt")
			If opRowFile <> "" Then
				ThisApplication.Documents.Open(opRowFile)
			End If
		Next
		opFactory.DefaultRow=opFactory.TableRows.Item(currow)
	End If
	
	MsgBox("Done")
	
End Sub

' Find the drawing for the specified part of assembly.
Function FindDrawingFileByName(PartOrAssemblyDoc As String)
    Dim fullFilename As String
    fullFilename = PartOrAssemblyDoc
	
    ' Extract the path from the full filename.
    Dim path As String
    path = ThisApplication.DesignProjectManager.ActiveDesignProject.WorkspacePath
   
    ' Extract the filename from the full filename.
    Dim filename As String
    filename = Right$(fullFilename, Len(fullFilename) - InStrRev(fullFilename, "\"))
   
    ' Replace the extension with "dwg"
    filename = Left$(filename, InStrRev(filename, ".")) & "dwg"
   
    ' Find if the drawing exists.
    Dim drawingFilename As String
    drawingFilename = ThisApplication.DesignProjectManager.ResolveFile(path, filename)
   
    ' Check the result.
    If drawingFilename = "" Then
        ' Try again with idw extension.
        filename = Left$(filename, InStrRev(filename, ".")) & "idw"
       
        ' Find if the drawing exists.
        drawingFilename = ThisApplication.DesignProjectManager.ResolveFile(path, filename)
   
        ' Return the result.
        If drawingFilename <> "" Then
            FindDrawingFileByName = drawingFilename
        Else
            FindDrawingFileByName = ""
        End If
    Else
        ' Return the result.
        FindDrawingFileByName = drawingFilename
    End If
End Function
