'Author: Cody Redding
'contact: codered741@gmail.com

'Runs in an Assembly to give all first level components a random color.  
'Procedure:
' Get all first level components
' Create/Switch to new view rep ("Pretty Colors")
' iterate through the components
'  select all instances
'  generate a random color
'  assign color to instances

Sub Main()
    Dim oAsmDoc As AssemblyDocument = ThisApplication.ActiveDocument
	Dim oAsmDef As AssemblyComponentDefinition = oAsmDoc.ComponentDefinition
	Dim dViewRepMgr As RepresentationsManager = oAsmDef.RepresentationsManager
	Dim dViewReps As DesignViewRepresentations = dViewRepMgr.DesignViewRepresentations
	Dim dMasterViewRep As DesignViewRepresentation = dViewReps.Item(1) 'assume that the first view rep is the master
	Dim vRepName As String = "Pretty Colors" 'name for the new view rep
	Dim dPCViewRep As DesignViewRepresentation 
	Dim oOccs as ComponentOccurrencesEnumerator
	Dim PCVRepOn as Boolean = False
	Dim UsedColors as New List(of Integer)
	Dim BreakLoop as Integer ' used to prevent possible infinite loop
	Dim ColorsCount as Integer = 194
	
	Try
		dPCViewRep = dViewReps.Item(vRepName)
	Catch 
		dMasterViewRep.Activate()
		dViewReps.Add(vRepName)
		PCVRepOn = True
	End Try 
	
	IF PCVRepOn = False Then
		dPCViewRep.Activate()
    End If
	
	' Initialize the random number generator and get
    ' the number of render styles defined.
	Randomize
    Dim iColorCount As Long
    iColorCount = oAsmDoc.RenderStyles.Count
	
	If oAsmDoc.AllReferencedDocuments.Count > 50 Then
		uCont = MessageBox.Show("This assembly has a large number of parts.  This operation may take some time.  Are you sure you want to continue?", "iLogic", MessageBoxButtons.OKCancel, MessageBoxIcon.Question)
		If uCont = vbCancel Then
			Exit Sub
		End If
	End If
	
	If oAsmDoc.AllReferencedDocuments.Count > ColorsCount Then '194 RAL colors
		uCont = MessageBox.Show("This assembly has more parts than available distinct colors.  The operation will be canceled.  ", "iLogic", MessageBoxButtons.OK, MessageBoxIcon.Error)
		Exit Sub
	End If
	
	
		
	For Each refDoc in oAsmDoc.AllReferencedDocuments
		If refDoc.DocumentType = kPartDocumentObject Then
			oOccs = oAsmDef.Occurrences.AllReferencedOccurrences(refDoc)
		
			BreakLoop = 0
		
		loop1:

			pColor = Int((iColorCount * Rnd) + 1)
			
			If oAsmDoc.RenderStyles.Item(pColor).Name.Contains("RAL") OrElse UsedColors.Contains(pColor) Then
				'Do nothing
			Else
				
				BreakLoop += 1
				
				If BreakLoop > ColorsCount Then
					MessageBox.Show("An error occurred, please try again", "iLogic Error", MessageBoxButtons.OK, MessageBoxIcon.Error)
					Exit Sub
				End If
				
				GoTo loop1 'pick a new color, until an unused RAL color is selected.  
				
			End If
			
			For Each oOcc In oOccs
				oOcc.SetRenderStyle(kOverrideRenderStyle, oAsmDoc.RenderStyles.Item(pColor))
			Next
			
			UsedColors.Add(pColor)
			
		End If
	Next
	
End Sub 'Main
